#usage	"<h1>IPC Footprint Wizard Installer</h1>"
		"<p>IPC Footprint Wizard Installer</p>"
		"Author: <author>Simon Reuter</author>"
		
string ulpDir = filedir(argv[0]);
if (strxstr(cfgget("EAGLE:Directories.Ulp"), ulpDir) == -1 && strxstr(cfgget("EAGLE:Directories.Ulp"), strsub(ulpDir,0,strlen(ulpDir)-1)) == -1) {
	cfgset("EAGLE:Directories.Ulp",cfgget("EAGLE:Directories.Ulp")+";"+ulpDir);
}

string ipcWizardCmd = "MENU '[" + ulpDir + "ipc-wizard/icons/ipc_wizard_new.svg] IPC Wizard : RUN ipc-wizard.ulp';\n";
string ipcEditCmd = "MENU '[" + ulpDir + "ipc-wizard/icons/ipc_wizard_edit.svg] IPC Edit : RUN ipc-edit.ulp';\n";
string resizeIconCmd = "RUN '" + ulpDir + "common/resize-icons.ulp' '" + ulpDir + "ipc-wizard/icons/master/' '" + ulpDir + "ipc-wizard/icons/';\n";

string outScr = "";
outScr += "RUN add-to-eagle-scr.ulp LBR " + resizeIconCmd;
outScr += "RUN add-to-eagle-scr.ulp PAC " + resizeIconCmd;
outScr += "RUN add-to-eagle-scr.ulp LBR " + ipcWizardCmd;
outScr += "RUN add-to-eagle-scr.ulp PAC " + ipcWizardCmd;
outScr += "RUN add-to-eagle-scr.ulp PAC " + ipcEditCmd;

exit (outScr);
